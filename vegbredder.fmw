FME workspace vegbredder.fmw

Parameters:
- DestDataset_OGCGEOPACKAGE = $(FME_MF_DIR)testoutput.gpkg   # GeoPackage File
- SourceDataset_OGCGEOPACKAGE_8 = C:\DATA\temp\manuelt.gpkg   # GeoPackage File
- DestDataset_FILEGDB = C:\DATA\temp\smalveg_20201208.gdb   # File Geodatabase
- SourceDataset_OGCGEOPACKAGE_10 = $(FME_MF_DIR)nvdbdata.gpkg   # GeoPackage File

Readers:
- OGCGEOPACKAGE_5: OGCGEOPACKAGE from $(SourceDataset_OGCGEOPACKAGE_8)
- OGCGEOPACKAGE_7: OGCGEOPACKAGE from $(SourceDataset_OGCGEOPACKAGE_10)

Writers:
- OGCGEOPACKAGE_6: OGCGEOPACKAGE to $(DestDataset_OGCGEOPACKAGE)
- FILEGDB_1: FILEGDB to $(DestDataset_FILEGDB)

type5_rekkverk (reader OGCGEOPACKAGE_7)
    attributes: objekttype int, nvdbId int, versjon int, startdato text, Rekkverkstype text, Lengde double, Stolpeavstand double, Bruksområde text, Skinneutrustning text, veglenkesekvensid int, detaljnivå text, typeVeg text, kommune int, fylke int, vref text, vegkategori text, fase text, nummer int, startposisjon double, sluttposisjon double, segmentlengde double, adskilte_lop text, trafikantgruppe text, Styrkeklasse text, MC-skinne text, Utgår_Type skinne text, Vedlikeholdsansvarlig text, Eier text, Tilleggsinformasjon text, Utblokking text,
      Håndlist text, Etableringsår double, Elementlengde double, Høyde double, Prosjektreferanse text, Plassering på bru text, Rekkverksbredde double, FKB_ID text, Panel text, Produktnavn/typegodkjenning text
    -> Bufferer
type99_vegoppmerking_langsgående (reader OGCGEOPACKAGE_7)
    attributes: objekttype int, nvdbId int, versjon int, startdato text, Type text, Bredde, enkeltlinje double, Linjemønster text, Materialtype text, Bruksområde text, Nedfresing text, Farge text, Vegbanereflektor text, Profilering text, veglenkesekvensid int, detaljnivå text, typeVeg text, kommune int, fylke int, vref text, vegkategori text, fase text, nummer int, startposisjon double, sluttposisjon double, segmentlengde double, adskilte_lop text, trafikantgruppe text, Tykkelse double, Løpemeter skravur double, Areal av fylt sperreområde double,
      Lengde omslutningslinje double, Vedtaksnummer text, Prosjektreferanse text, Lengde double, Tilleggsinformasjon text
    -> type99_vegoppmerking_langsgående
    -> Bufferer
Bufferer
    ANGLE = 22.5
    CAP_STYLE = Round
    CORNER_STYLE = Arc
    MODE = AREA
    OFFSET = 1
    OFFSET_UNITS = NONE
    PRECISION = APPROX
    BUFFERED -> Bufferer_Buffered
    BUFFERED -> LineOnAreaOverlayer [AREA]
Bufferer_Buffered: Inspector [off]
type99_vegoppmerking_langsgående: Inspector
vegnett (reader OGCGEOPACKAGE_7)
    attributes: href text, veglenkesekvensid int, startposisjon double, sluttposisjon double, kortform text, veglenkenummer int, segmentnummer int, startnode text, sluttnode text, referanse text, type text, detaljnivå text, typeVeg text, typeVeg_sosi text, målemetode text, måledato text, feltoversikt text, lengde double, fylke int, kommune int, vegsystemreferanse text, startdato text, vref text, vegkategori text, fase text, nummer int, strekning double, delstrekning double, ankerpunktmeter double, sideanleggsdel double,
      trafikantgruppe text, fra_meter double, til_meter double, adskilte_lop text, kryssdel double, topologinivå text, superstedfesting text
    -> Tester_6
LineOnAreaOverlayer
    ATTR_ACCUM_MODE = Merge Incoming
    ATTR_CONFLICT_RES = Use Original
    CANDIDATE_LIST_ATTRS_TO_INCLUDE_MODE = Selected Attributes
    CLEANING_TOLERANCE = Automatic
    DEAGGREGATE_INPUT = Yes
    OV_ATTR = _overlaps
    LINE -> Tester_4
    <REJECTED> -> LineOnAreaOverlayer__Rejected_
Tester_4
    BOOL_OP = OR
    COMPOSITE_TEST = 1
    TEST_CLAUSE = TEST @Value(_overlaps) = 0
    TEST_MODE = TEST
    PASSED -> AttributeExposer
vegbredde583: Inspector
vegbreddePMS: Inspector
vegbreddeFKB: Inspector
Bufferer_2
    ANGLE = 22.5
    CAP_STYLE = Arc
    CORNER_STYLE = Arc
    MODE = AREA
    OFFSET = 2
    OFFSET_UNITS = NONE
    PRECISION = APPROX
    BUFFERED -> LineOnAreaOverlayer_2 [AREA]
TestFilter__Unfiltered_: Inspector [off]
TestFilter_vegnett: Inspector [off]
LineOnAreaOverlayer__Rejected_: Inspector [off]
feilTopo: Inspector [off]
inkluder (reader OGCGEOPACKAGE_5) [off]
    attributes: Navn text
    -> LineOnAreaOverlayer_2 [AREA]
LineOnAreaOverlayer_2
    ATTR_ACCUM_MODE = Merge Incoming
    ATTR_CONFLICT_RES = Use Original
    CANDIDATE_LIST_ATTRS_TO_INCLUDE_MODE = Selected Attributes
    CLEANING_TOLERANCE = Automatic
    DEAGGREGATE_INPUT = Yes
    OV_ATTR = _overlaps
    LINE -> Tester_7
Tester_7
    BOOL_OP = OR
    COMPOSITE_TEST = 1
    TEST_CLAUSE = TEST @Value(_overlaps) > 0
    TEST_MODE = TEST
    PASSED -> Smal_veg
    PASSED -> LineOnAreaOverlayer_3 [LINE]
Smal_veg: Inspector [off]
ekskluder (reader OGCGEOPACKAGE_5) [off]
    attributes: navn text
    -> LineOnAreaOverlayer_3 [AREA]
LineOnAreaOverlayer_3
    ATTR_ACCUM_MODE = Merge Incoming
    ATTR_CONFLICT_RES = Use Original
    CANDIDATE_LIST_ATTRS_TO_INCLUDE_MODE = Selected Attributes
    CLEANING_TOLERANCE = Automatic
    DEAGGREGATE_INPUT = Yes
    OV_ATTR = _overlaps
    LINE -> Tester_8
Tester_8
    BOOL_OP = OR
    COMPOSITE_TEST = 1
    TEST_CLAUSE = TEST @Value(_overlaps) = 0
    TEST_MODE = TEST
    PASSED -> AttributeSplitter
AttributeSplitter
    ATTR_NAME = vref
    DELIMITER = " "
    DROP_EMPTY_PARTS = No
    LIST_NAME = _list
    TRIM_OPTION = Both
    -> AttributeCreator
AttributeCreator
    ATTR_TABLE = SET_TO vegnummer = @Value(_list{0})
    -> AttributeKeeper
AttributeKeeper
    CREATE_BULK_MODE_FEATURES = NO
    KEEP_ATTRS = fylke,kommune,vegkategori,vref,vegnummer
    -> LengthCalculator
LengthCalculator
    DIM = 2
    LEN_ATTR = lengde
    MULT = 1
    -> AttributeRenamer
AttributeRenamer
    ATTR_TABLE = RENAME_SET_DEFAULT vref > vegreferanse
    -> LengthCalculator_Output
    -> smaleveger_2020des12 (writer FILEGDB_1)
    -> test_Smalveg (writer OGCGEOPACKAGE_6)
test_Smalveg (writer OGCGEOPACKAGE_6)
    attributes: vegreferanse text, vegnummer text(200), fylke int, kommune int, vegkategori text, lengde double
smaleveger_2020des12 (writer FILEGDB_1) [off]
    attributes: vegreferanse text(2048), vegnummer text(200), fylke text(20), kommune text(20), vegkategori text(2048), lengde double
LengthCalculator_Output: Inspector

Bookmark: Vegbredde
type583_vegbredde (reader OGCGEOPACKAGE_7)
    attributes: objekttype int, nvdbId int, versjon int, startdato text, Vegbredde, totalt double, Dekkebredde double, Dato registrert text, Dataopprinnelse text, veglenkesekvensid int, detaljnivå text, typeVeg text, kommune int, fylke int, vref text, vegkategori text, fase text, nummer int, startposisjon double, sluttposisjon double, segmentlengde double, adskilte_lop text, trafikantgruppe text, Kjørebanebredde double, Målemetode text
    -> Tester_3
Tester_3
    BOOL_OP = COMPOSITE
    COMPOSITE_TEST = 1 AND 2
    TEST_CLAUSE:
      TEST @Value(Vegbredde, totalt) <= 6,5
      TEST Vegbredde, totalt ATTRIBUTE_HAS_A_VALUE ""
    TEST_MODE = TEST
    PASSED -> Tester_5
type647_statistikk_vegbredde (reader OGCGEOPACKAGE_7)
    attributes: objekttype int, nvdbId int, versjon int, startdato text, Geografisk oppløsning text, Midlere dekkebredde double, Midlere kjørebanebredde double, Midlere vegbredde double, Dekkeareal int, Målt % double, Opprettet dato text, Minimumsdato, grunnlag text, Maksimumsdato, grunnlag text, Lengde int, Stedsangivelse, fra-til text, veglenkesekvensid int, detaljnivå text, typeVeg text, kommune int, fylke int, vref text, vegkategori text, fase text, nummer int, startposisjon double, sluttposisjon double, segmentlengde double, adskilte_lop text, trafikantgruppe text
    -> Tester_2
Tester_2
    BOOL_OP = OR
    COMPOSITE_TEST = 1
    TEST_CLAUSE = TEST @Value(Midlere vegbredde) <= 6,5
    TEST_MODE = TEST
    PASSED -> Tester_5
type838_vegbredde_beregnet (reader OGCGEOPACKAGE_7)
    attributes: objekttype int, nvdbId int, versjon int, startdato text, Dekkebredde, maks double, Dekkebredde double, Dekkebredde, min double, Kvalitet grunnlag double, Beregningsinfo text, Dato grunnlag text, Grunnlag text, Målemetode grunnlag text, veglenkesekvensid int, detaljnivå text, typeVeg text, kommune int, fylke int, vref text, vegkategori text, fase text, nummer int, startposisjon double, sluttposisjon double, segmentlengde double, adskilte_lop text, trafikantgruppe text, Dekkebredde, median double, Dekkebredde, normal double, Vegbredde, maks double, Vegbredde double,
      Vegbredde, min double, Kjørebanebredde, maks double, Kjørebanebredde double, Kjørebanebredde, min double
    -> Tester
Tester
    BOOL_OP = COMPOSITE
    COMPOSITE_TEST = 1 AND 2 AND 3 AND 4 AND 5
    TEST_CLAUSE:
      TEST @Value(Dekkebredde, min) < 6,5
      TEST @Value(Kjørebanebredde) < 6,5
      TEST @Value(Dekkebredde) < 6,5
      TEST @Value(Vegbredde) < 6,5
      TEST @Value(Vegbredde, min) < 6,5
    TEST_MODE = TEST
    PASSED -> Tester_5

Bookmark: Filtrere...
Tester_6
    BOOL_OP = AND
    COMPOSITE_TEST = 1 AND 2 AND 3 AND 4 AND 5
    TEST_CLAUSE:
      CASE_INSENSITIVE_TEST @Value(detaljnivå) CONTAINS Vegtras
      TEST @Value(type) = HOVED
      TEST @Value(typeVeg) != Bilferje
      TEST @Value(typeVeg) != Beredskapsveg
      TEST @Value(typeVeg) != Serviceveg
    TEST_MODE = PER_TEST
    PASSED -> TestFilter_2
    FAILED -> feilTopo
TestFilter_2
    DEFAULT_VALUE = <UNFILTERED>
    TEST_LIST = "BOOL_OP,AND,COMPOSITE_TEST,""""""1"""""",TEST_CLAUSE,CASE_INSENSITIVE_TEST @Value(vref) CONTAINS RV41 S1D1 m2145-2160",RV41 S1D1 m2145-2160,"BOOL_OP,AND,COMPOSITE_TEST,""""""1"""""",TEST_CLAUSE,CASE_INSENSITIVE_TEST @Value(vref) CONTAINS RV41 S1D1 m49",RV41 S1D1 m49
    <UNFILTERED> -> Tester_5
Tester_5
    BOOL_OP = AND
    COMPOSITE_TEST = 1 AND 2 AND 3 AND 4
    TEST_CLAUSE:
      TEST @Value(typeVeg) != Rampe
      TEST @Value(typeVeg) != Rundkjøring
      TEST @Value(trafikantgruppe) = K
      TEST @Value(adskilte_lop) = Nei
    TEST_MODE = TEST
    PASSED -> TestFilter_4
    FAILED -> Tester_5_Failed
Note: TestFilter_4 [TestFilter] / Port Definitions: Test ConditionOutput PortIfCASE_INSENSITIVE_TEST @Value(vref) CONTAINS RV22 / Composite Test: 1rv22Else IfCASE_INSENSITIVE_TEST @Value(vref) CONTAINS RV22 / Composite Test: 1RV41 S20Else IfCASE_INSENSITIVE_TEST @Value(vref) CONTAINS RV25 / Composite Test: 1RV25Else IfCASE_INSENSITIVE_TEST @Value(vref) CONTAINS EV18 / Composite Test: 1EV18Else IfCASE_INSENSITIVE_TEST @Value(vref) CONTAINS RV19 / Composite Test: 1RV19Else IfCASE_INSENSITIVE_TEST @Value(vref) CONTAINS EV6 S7D10 / Composite Test: 1EV6 S7D10Else IfCASE_INSENSITIVE_TEST @Value(vref) CONTAINS RV204 / Composite Test: 1RV204Else IfCASE_INSENSITIVE_TEST @Value(vref) CONTAINS EV18 / Composite Test: 1EV18Else IfCASE_INSENSITIVE_TEST @Value(vref) CONTAINS EV134 S49 / Composite Test: 1 EV134 S49Else IfCASE_INSENSITIVE_TEST @Value(vref) CONTAINS RV162 / Composite Test: 1RV162Else IfCASE_INSENSITIVE_TEST @Value(vref) CONTAINS RV4 / Composite Test: 1RV4Else IfCASE_INSENSITIVE_TEST @Value(vref) CONTAINS EV6 S31D50 / Composite Test: 1EV6 S31D50Else IfCASE_INSENSITIVE_TEST @Value(vref) CONTAINS EV6 S32D1 / Composite Test: 1EV6 S32D1Else IfCASE_INSENSITIVE_TEST @Value(vref) CONTAINS EV6 S37D20 / Composite Test: 1EV6 S37D20Else IfCASE_INSENSITIVE_TEST @Value(vref) CONTAINS EV39 S107 / Composite Test: 1EV39 S107Else<All Other Conditions><Unfiltered>
TestFilter_4
    DEFAULT_VALUE = <UNFILTERED>
    TEST_LIST = "BOOL_OP,OR,COMPOSITE_TEST,""""""1"""""",TEST_CLAUSE,CASE_INSENSITIVE_TEST @Value(vref) CONTAINS RV22",rv22,"BOOL_OP,OR,COMPOSITE_TEST,""""""1"""""",TEST_CLAUSE,CASE_INSENSITIVE_TEST @Value(vref) CONTAINS RV22",RV41 S20,"BOOL_OP,OR,COMPOSITE_TEST,""""""1"""""",TEST_CLAUSE,CASE_INSENSITIVE_TEST @Value(vref) CONTAINS RV25",RV25,"BOOL_OP,OR,COMPOSITE_TEST,""""""1"""""",TEST_CLAUSE,CASE_INSENSITIVE_TEST @Value(vref) CONTAINS EV18",EV18,"BOOL_OP,OR,COMPOSITE_TEST,""""""1"""""",TEST_CLAUSE,CASE_INSENSITIVE_TEST @Value(vref) CONTAINS RV19",RV19,"BOOL_OP,OR,COMPOSITE_TEST,""""""1"""""",TEST_CLAUSE,CASE_INSENSITIVE_TEST @Value(vref) CONTAINS EV6 S7D10",EV6 S7D10,"BOOL_OP,OR,COMPOSITE_TEST,""""""1"""""",TEST_CLAUSE,CASE_INSENSITIVE_TEST @Value(vref) CONTAINS RV204",RV204,"BOOL_OP,OR,COMPOSITE_TEST,""""""1"""""",TEST_CLAUSE,CASE_INSENSITIVE_TEST @Value(vref) CONTAINS EV18",EV18,"BOOL_OP,OR,COMPOSITE_TEST,""""""1"""""",TEST_CLAUSE,CASE_INSENSITIVE_TEST @Value(vref) CONTAINS  EV134 S49", EV134 S49,"BOOL_OP,OR,COMPOSITE_TEST,""""""1"""""",TEST_CLAUSE,CASE_INSENSITIVE_TEST @Value(vref) CONTAINS RV162",RV162,"BOOL_OP,OR,COMPOSITE_TEST,""""""1"""""",TEST_CLAUSE,CASE_INSENSITIVE_TEST @Value(vref) CONTAINS RV4 ",RV4,"BOOL_OP,OR,COMPOSITE_TEST,""""""1"""""",TEST_CLAUSE,CASE_INSENSITIVE_TEST @Value(vref) CONTAINS EV6 S31D50",EV6 S31D50,"BOOL_OP,OR,COMPOSITE_TEST,""""""1"""""",TEST_CLAUSE,CASE_INSENSITIVE_TEST @Value(vref) CONTAINS EV6 S32D1",EV6 S32D1,"BOOL_OP,OR,COMPOSITE_TEST,""""""1"""""",TEST_CLAUSE,CASE_INSENSITIVE_TEST @Value(vref) CONTAINS EV6 S37D20",EV6 S37D20,"BOOL_OP,OR,COMPOSITE_TEST,""""""1"""""",TEST_CLAUSE,CASE_INSENSITIVE_TEST @Value(vref) CONTAINS EV39 S107",EV39 S107
    rv22 -> TestFilter_4_rv22
    RV41 S20 -> TestFilter_4_RV41_S20
    RV25 -> TestFilter_4_RV25
    EV18 -> TestFilter_4_EV18
    RV4 -> TestFilter_4_RV4
    <UNFILTERED> -> TestFilter_3
TestFilter_4_rv22: Inspector
TestFilter_4_RV41_S20: Inspector
TestFilter_4_RV25: Inspector
TestFilter_4_EV18: Inspector
TestFilter_4_RV4: Inspector
TestFilter_3
    DEFAULT_VALUE = <UNFILTERED>
    TEST_LIST = "BOOL_OP,OR,COMPOSITE_TEST,""""""1"""""",TEST_CLAUSE,CASE_INSENSITIVE_TEST @Value(vref) CONTAINS KD",kryssdel,"BOOL_OP,OR,COMPOSITE_TEST,""""""1"""""",TEST_CLAUSE,CASE_INSENSITIVE_TEST @Value(vref) CONTAINS SD",sideanlegg,"BOOL_OP,OR,COMPOSITE_TEST,""""""1"""""",TEST_CLAUSE,TEST @Value(typeVeg) = Kanalisert veg",Kanalisert veg
    <UNFILTERED> -> LineOnAreaOverlayer [LINE]
Tester_5_Failed: Inspector [off]

Bookmark: New Bookmark
AttributeExposer
    ATTR_LIST = fme_feature_type
    -> TestFilter
TestFilter
    DEFAULT_VALUE = <UNFILTERED>
    TEST_LIST = "BOOL_OP,OR,COMPOSITE_TEST,""""""1"""""",TEST_CLAUSE,CASE_INSENSITIVE_TEST @Value(fme_feature_type) CONTAINS type583",vegbredde583,"BOOL_OP,OR,COMPOSITE_TEST,""""""1"""""",TEST_CLAUSE,CASE_INSENSITIVE_TEST @Value(fme_feature_type) CONTAINS type647",PMSvegbredde,"BOOL_OP,OR,COMPOSITE_TEST,""""""1"""""",TEST_CLAUSE,CASE_INSENSITIVE_TEST @Value(fme_feature_type) CONTAINS type838",FKBvegbredde,"BOOL_OP,OR,COMPOSITE_TEST,""""""1"""""",TEST_CLAUSE,CASE_INSENSITIVE_TEST @Value(fme_feature_type) CONTAINS vegnett",vegnett
    vegbredde583 -> vegbredde583
    vegbredde583 -> Bufferer_2
    PMSvegbredde -> vegbreddePMS
    PMSvegbredde -> Bufferer_2
    FKBvegbredde -> Bufferer_2
    FKBvegbredde -> vegbreddeFKB
    vegnett -> TestFilter_vegnett
    vegnett -> LineOnAreaOverlayer_2 [LINE]
    <UNFILTERED> -> TestFilter__Unfiltered_
